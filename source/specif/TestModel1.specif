# UML data extracted from Sparx Enterprise Architect: TestModel1.eap

## Integer (RC-UML_PassiveElement)
- dcterms:description: An instance of Integer is a value in the (infinite) set of integers (…-2, -1, 0, 1, 2…).
- dcterms:type: OMG:UML:2.5.1:PrimitiveType

## Boolean (RC-UML_PassiveElement)
- dcterms:description: An instance of Boolean is one of the predefined values true and false.
- dcterms:type: OMG:UML:2.5.1:PrimitiveType

## String (RC-UML_PassiveElement)
- dcterms:description: An instance of String defines a sequence of characters. Character sets may include non-Roman
  alphabets.The semantics of the string itself depends on its purpose; it can be a comment,
  computational language expression, OCL expression, etc.
- dcterms:type: OMG:UML:2.5.1:PrimitiveType

## UnlimitedNatural (RC-UML_PassiveElement)
- dcterms:description: An instance of UnlimitedNatural is a value in the (infinite) set of natural numbers (0, 1, 2…) plus
  unlimited. The value of unlimited is shown using an asterisk (‘*’). UnlimitedNatural values are
  typically used to denote the upper bound of a range, such as a multiplicity; unlimited is used
  whenever the range is specified to have no upper bound.
- dcterms:type: OMG:UML:2.5.1:PrimitiveType

## Real (RC-UML_PassiveElement)
- dcterms:description: An instance of Real is a value in the (infinite) set of real numbers. Typically an implementation
  will internally represent Real numbers using a floating point standard such as ISO/IEC/IEEE
  60559:2011 (whose content is identical to the predecessor IEEE 754 standard).
- dcterms:type: OMG:UML:2.5.1:PrimitiveType

## Test Model 1 (RC-UML_Package)
- UML:VisibilityKind: V-UML_VisibilityKind-0

## Diagrams (RC-UML_Package)
- SpecIF:Stereotype: diagrams
- UML:VisibilityKind: V-UML_VisibilityKind-0

## Test Model 1 (RC-Diagram)
- dcterms:description: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
- SpecIF:Notation: OMG:UML:2.5.1:Class Diagram

## Elements (RC-UML_Package)
- UML:VisibilityKind: V-UML_VisibilityKind-0

## Car (RC-UML_PassiveElement)
- dcterms:type: OMG:UML:2.5.1:Class
- UML:VisibilityKind: V-UML_VisibilityKind-0

## Maximum Speed (RC-UML_ActiveElement)
- dcterms:type: OMG:UML:2.5.1:Attribute
- rdf:value: 15
- UML:VisibilityKind: V-UML_VisibilityKind-0

## accelerate (RC-UML_ActiveElement)
- dcterms:description: Accelerate the vehicle.
- dcterms:type: OMG:UML:2.5.1:Operation
- SpecIF:Stereotype: :
- UML:VisibilityKind: V-UML_VisibilityKind-0

## op2 (RC-UML_ActiveElement)
- dcterms:type: OMG:UML:2.5.1:Operation
- SpecIF:Stereotype: :
- UML:VisibilityKind: V-UML_VisibilityKind-0

## param1 (RC-UML_ActiveElement)
- dcterms:type: OMG:UML:2.5.1:Parameter

## Vehicle (RC-UML_PassiveElement)
- dcterms:type: OMG:UML:2.5.1:Class
- UML:VisibilityKind: V-UML_VisibilityKind-0

## Multiplicity (RC-UML_ActiveElement)
- dcterms:description: Values: Single,Multiple
  Default: Single
- dcterms:type: OMG:UML:2.5.1:TaggedValue
- rdf:value: Single
- SpecIF:Stereotype: FMC4SE:agent

## Type (RC-UML_ActiveElement)
- dcterms:description: Values: Standard,Software,Chain,Electronic,Mechanical
  Default: Standard
- dcterms:type: OMG:UML:2.5.1:TaggedValue
- rdf:value: Standard
- SpecIF:Stereotype: FMC4SE:agent

## VW (RC-UML_ActiveElement)
- SpecIF:Stereotype: FMC4SE:agent
- dcterms:type: OMG:UML:2.5.1:Object
- UML:VisibilityKind: V-UML_VisibilityKind-0

## Statements
- Test Model 1 SpecIF:contains Diagrams
- Diagrams SpecIF:contains Test Model 1
- Test Model 1 SpecIF:contains Elements
- Elements SpecIF:contains Car
- Car UML:Relationship Vehicle
- Elements SpecIF:contains Vehicle
- Maximum Speed rdf:type Integer
- accelerate rdf:type Boolean
- op2 rdf:type Vehicle
- op2 SpecIF:contains param1
- param1 rdf:type Boolean
- Vehicle SpecIF:contains Maximum Speed
- Vehicle SpecIF:contains accelerate
- Vehicle SpecIF:contains op2
- Elements SpecIF:contains VW
- VW SpecIF:contains Multiplicity
- VW SpecIF:contains Type
- VW rdf:type Car
